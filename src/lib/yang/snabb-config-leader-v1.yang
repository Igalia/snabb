module snabb-config-leader-v1 {
  namespace snabb:config-leader;
  prefix config-leader;

  organization "Igalia, S.L.";
  contact "Andy Wingo <wingo@igalia.com>";
  description
   "RPC interface for ConfigLeader Snabb app.";

  revision 2016-12-20 {
    description "Add basic error reporting.";
  }

  revision 2016-11-12 {
    description
     "Initial revision.";
  }

  grouping error-reporting {
    leaf status { type uint8; default 0; }
    leaf error { type string; }
  }

  rpc describe {
    output {
      leaf native-schema { type string; mandatory true; }
      leaf-list alternate-schema { type string; }
      list capability {
        key module;
        leaf module { type string; }
        leaf-list feature { type string; }
      }
    }
  }

  rpc get-config {
    input {
      leaf schema { type string; mandatory true; }
      leaf revision { type string; }
      leaf path { type string; default "/"; }
      leaf print-default { type boolean; }
      leaf format { type string; }
    }
    output {
      uses error-reporting;
      leaf config { type string; }
    }
  }

  rpc set-config {
    input {
      leaf schema { type string; mandatory true; }
      leaf revision { type string; }
      leaf path { type string; default "/"; }
      leaf config { type string; mandatory true; }
    }
    output {
      uses error-reporting;
    }
  }

  rpc add-config {
    input {
      leaf schema { type string; mandatory true; }
      leaf revision { type string; }
      leaf path { type string; mandatory true; }
      leaf config { type string; mandatory true; }
    }
    output {
      uses error-reporting;
    }
  }

  rpc remove-config {
    input {
      leaf schema { type string; mandatory true; }
      leaf revision { type string; }
      leaf path { type string; mandatory true; }
    }
    output {
      uses error-reporting;
    }
  }

  rpc get-state {
    input {
      leaf schema { type string; mandatory true; }
      leaf revision { type string; }
      leaf path { type string; default "/"; }
      leaf print-default { type boolean; }
      leaf format { type string; }
    }
    output {
      uses error-reporting;
      leaf state { type string; }
    }
  }

  rpc attach-listener {
    input {
      leaf schema { type string; mandatory true; }
      leaf revision { type string; }
    }
    output {
      uses error-reporting;
    }
  }

  rpc compress-alarms {
    /* XXX: Not actual input arguments specified in ietf-alarms */
    input {
      leaf schema { type string; mandatory true; }
      leaf revision { type string; }
      leaf path { type string; default "/"; }
    }
    output {
      uses error-reporting;
      leaf compressed-alarms {
        type uint32;
        description
          "Number of compressed alarm entries.";
      }
    }
  }

  rpc purge-alarms {
    /* XXX: Not actual input arguments specified in ietf-alarms */
    input {
      leaf schema { type string; mandatory true; }
      leaf revision { type string; }
      leaf path { type string; default "/"; }
    }
    output {
      uses error-reporting;
      leaf purged-alarms {
        type uint32;
        description
          "Number of purged alarms.";
      }
    }
  }

}
